FME workspace ParksAsset_WKT.fmw

Parameters:
- SourceDataset_GEODATABASE_MDB = K:\CITY\TRANSPORT\_PUBLIC\Asset Data\2018 12 10 DATA FOR ASSETIC\Parks Data\geodata\POS_17.mdb   # Source ESRI Geodatabase (MDB) File(s)
- DestDataset_CSV = J:\GISDATA\GIS_ASSET_DATA\P&G_AssetNew\Assetic\WKT   # Destination Comma Separated Value (CSV) Directory
- SourceDataset_GEODATABASE_MDB_33 = K:\CITY\TRANSPORT\_PUBLIC\Asset Data\2018 12 10 DATA FOR ASSETIC\Parks Data\geodata\POS_17.mdb   # Source ESRI Geodatabase (MDB) File(s)
- SourceDataset_GEODATABASE_MDB_25 = K:\CITY\TRANSPORT\_PUBLIC\Asset Data\2018 12 10 DATA FOR ASSETIC\Parks Data\geodata\POS_17.mdb   # Source ESRI Geodatabase (MDB) File(s)
- SourceDataset_GEODATABASE_MDB_21 = K:\CITY\TRANSPORT\_PUBLIC\Asset Data\2018 12 10 DATA FOR ASSETIC\Parks Data\geodata\POS_17.mdb   # Source ESRI Geodatabase (MDB) File(s)
- SourceDataset_GEODATABASE_MDB_29 = K:\CITY\TRANSPORT\_PUBLIC\Asset Data\2018 12 10 DATA FOR ASSETIC\Parks Data\geodata\POS_17.mdb   # Source ESRI Geodatabase (MDB) File(s)
- SourceDataset_GEODATABASE_MDB_19 = K:\CITY\TRANSPORT\_PUBLIC\Asset Data\2018 12 10 DATA FOR ASSETIC\Parks Data\geodata\POS_17.mdb   # Source ESRI Geodatabase (MDB) File(s)
- SourceDataset_GEODATABASE_MDB_23 = K:\CITY\TRANSPORT\_PUBLIC\Asset Data\2018 12 10 DATA FOR ASSETIC\Parks Data\geodata\POS_17.mdb   # Source ESRI Geodatabase (MDB) File(s)
- SourceDataset_GEODATABASE_MDB_27 = K:\CITY\TRANSPORT\_PUBLIC\Asset Data\2018 12 10 DATA FOR ASSETIC\Parks Data\geodata\POS_17.mdb   # Source ESRI Geodatabase (MDB) File(s)
- SourceDataset_GEODATABASE_MDB_31 = K:\CITY\TRANSPORT\_PUBLIC\Asset Data\2018 12 10 DATA FOR ASSETIC\Parks Data\geodata\POS_17.mdb   # Source ESRI Geodatabase (MDB) File(s)
- SourceDataset_GEODATABASE_MDB_35 = K:\CITY\TRANSPORT\_PUBLIC\Asset Data\2018 12 10 DATA FOR ASSETIC\Parks Data\geodata\POS_17.mdb   # Source ESRI Geodatabase (MDB) File(s)
- SourceDataset_GEODATABASE_MDB_20 = K:\CITY\TRANSPORT\_PUBLIC\Asset Data\2018 12 10 DATA FOR ASSETIC\Parks Data\geodata\POS_17.mdb   # Source ESRI Geodatabase (MDB) File(s)
- SourceDataset_GEODATABASE_MDB_22 = K:\CITY\TRANSPORT\_PUBLIC\Asset Data\2018 12 10 DATA FOR ASSETIC\Parks Data\geodata\POS_17.mdb   # Source ESRI Geodatabase (MDB) File(s)
- SourceDataset_GEODATABASE_MDB_24 = K:\CITY\TRANSPORT\_PUBLIC\Asset Data\2018 12 10 DATA FOR ASSETIC\Parks Data\geodata\POS_17.mdb   # Source ESRI Geodatabase (MDB) File(s)
- SourceDataset_GEODATABASE_MDB_26 = K:\CITY\TRANSPORT\_PUBLIC\Asset Data\2018 12 10 DATA FOR ASSETIC\Parks Data\geodata\POS_17.mdb   # Source ESRI Geodatabase (MDB) File(s)
- SourceDataset_GEODATABASE_MDB_28 = K:\CITY\TRANSPORT\_PUBLIC\Asset Data\2018 12 10 DATA FOR ASSETIC\Parks Data\geodata\POS_17.mdb   # Source ESRI Geodatabase (MDB) File(s)
- SourceDataset_GEODATABASE_MDB_30 = K:\CITY\TRANSPORT\_PUBLIC\Asset Data\2018 12 10 DATA FOR ASSETIC\Parks Data\geodata\POS_17.mdb   # Source ESRI Geodatabase (MDB) File(s)
- SourceDataset_GEODATABASE_MDB_32 = K:\CITY\TRANSPORT\_PUBLIC\Asset Data\2018 12 10 DATA FOR ASSETIC\Parks Data\geodata\POS_17.mdb   # Source ESRI Geodatabase (MDB) File(s)
- SourceDataset_GEODATABASE_MDB_34 = K:\CITY\TRANSPORT\_PUBLIC\Asset Data\2018 12 10 DATA FOR ASSETIC\Parks Data\geodata\POS_17.mdb   # Source ESRI Geodatabase (MDB) File(s)

Readers:
- GEODATABASE_MDB_1: GEODATABASE_MDB from $(SourceDataset_GEODATABASE_MDB)
- GEODATABASE_MDB_2: GEODATABASE_MDB from $(SourceDataset_GEODATABASE_MDB_33)
- GEODATABASE_MDB_3: GEODATABASE_MDB from $(SourceDataset_GEODATABASE_MDB_25)
- GEODATABASE_MDB_4: GEODATABASE_MDB from $(SourceDataset_GEODATABASE_MDB_21)
- GEODATABASE_MDB_5: GEODATABASE_MDB from $(SourceDataset_GEODATABASE_MDB_29)
- GEODATABASE_MDB_6: GEODATABASE_MDB from $(SourceDataset_GEODATABASE_MDB_19)
- GEODATABASE_MDB_7: GEODATABASE_MDB from $(SourceDataset_GEODATABASE_MDB_23)
- GEODATABASE_MDB_8: GEODATABASE_MDB from $(SourceDataset_GEODATABASE_MDB_27)
- GEODATABASE_MDB_9: GEODATABASE_MDB from $(SourceDataset_GEODATABASE_MDB_31)
- GEODATABASE_MDB_10: GEODATABASE_MDB from $(SourceDataset_GEODATABASE_MDB_35)
- GEODATABASE_MDB_11: GEODATABASE_MDB from $(SourceDataset_GEODATABASE_MDB_20)
- GEODATABASE_MDB_12: GEODATABASE_MDB from $(SourceDataset_GEODATABASE_MDB_22)
- GEODATABASE_MDB_13: GEODATABASE_MDB from $(SourceDataset_GEODATABASE_MDB_24)
- GEODATABASE_MDB_14: GEODATABASE_MDB from $(SourceDataset_GEODATABASE_MDB_26)
- GEODATABASE_MDB_15: GEODATABASE_MDB from $(SourceDataset_GEODATABASE_MDB_28)
- GEODATABASE_MDB_16: GEODATABASE_MDB from $(SourceDataset_GEODATABASE_MDB_30)
- GEODATABASE_MDB_17: GEODATABASE_MDB from $(SourceDataset_GEODATABASE_MDB_32)
- GEODATABASE_MDB_18: GEODATABASE_MDB from $(SourceDataset_GEODATABASE_MDB_34)

Writers:
- CSV_1: CSV to $(DestDataset_CSV)

Backflow_Prevention (reader GEODATABASE_MDB_1)
    attributes: geodb_oid integer, OBJECTID integer, AST_NUM integer, VALVE_SIZE char(8), PG_MNTND smallint, COMMENTS char(50), AMEND_DATE date, AMEND_BY char(50), TYPE char(100), SECONDARY_ char(100), NAME char(100), SITE char(100), HANDOV_DAT date, COMP_TYPE smallint, AMEND_DA_1 date, AMEND_BY_1 char(20), SUB char(50), PARCEL integer, VARIATION smallint, Assetic_ID char(50), Asset_Subtype char(50), Asset_Type char(50)
    -> Reprojector
Reprojector
    DEST = EPSG:4326
    SOURCE = Read from feature
    RASTER_CELL_SIZE = Preserve Cells
    INTERPOLATION_TYPE_NAME = Nearest Neighbor
    STROKE_ARCS = Yes
    REPROJECTED -> GeometryExtractor
GeometryExtractor
    KIND_LONG = OGC Well Known Text
    ATTR = _geometry
    OGCVERSION = 1.1
    -> Backflow_Prevention (writer CSV_1)
Backflow_Prevention (writer CSV_1)
    attributes: Assetic_ID char(50), _geometry char(80)
BBQ (reader GEODATABASE_MDB_1)
    attributes: geodb_oid integer, OBJECTID_1 integer, OBJECTID integer, AST_NUM integer, TYPE char(50), PG_MNTND integer, COMP_TYPE smallint, SEQUENCE smallint, AMEND_DATE date, AMEND_BY char(20), FEATURE_TYPE char(25), SUB_TYPE char(15), COMMENTS char(200), PHOTO1 char(50), STRUCT char(50), FUNCT char(50), COND_RATE char(50), C_STATUS char(50), VARIATION smallint, PHOTO char(250), Asset_Subtype char(50), Assetic_ID char(50), Asset_Type char(50)
    -> Reprojector_2
Reprojector_2
    DEST = EPSG:4326
    SOURCE = Read from feature
    RASTER_CELL_SIZE = Preserve Cells
    INTERPOLATION_TYPE_NAME = Nearest Neighbor
    STROKE_ARCS = Yes
    REPROJECTED -> GeometryExtractor_2
GeometryExtractor_2
    KIND_LONG = OGC Well Known Text
    ATTR = _geometry
    OGCVERSION = 1.1
    -> BBQ (writer CSV_1)
BBQ (writer CSV_1)
    attributes: Assetic_ID char(50), _geometry char(80)
Boardwalk (reader GEODATABASE_MDB_1)
    attributes: geodb_oid integer, OBJECTID integer, Join_Count integer, AST_NUM integer, TYPE char(30), SECONDARY_ char(30), PG_MNTND integer, COMP_TYPE smallint, SEQUENCE smallint, AMEND_DATE date, AMEND_BY char(20), VARIATION smallint, COMMENTS char(200), PHOTO1 char(50), INSPECTOR char(20), INS_DATE date, STRUCT char(50), FUNCT char(50), COND_RATE char(50), C_STATUS char(50), Path char(97), Shape_Leng double, survey char(50), ASSET_ID double, INSPECTION char(20), INSPECTOR_ char(254), LATITUDE char(254), LONGITUDE double, LOCATION_D char(254), LOCATION_R char(254),
      PRIMARY_US char(254), TYPE_DESCR char(254), STRUCTURE_ char(254), BRIDGE_STR char(254), STRUCTUR00 double, NO_OF_BRID char(254), CULVERT_CE char(254), CONFIGURAT char(254), INSPECTI00 char(254), CONDITION_ char(254), X char(254), Y char(254), Z char(254), date_ date, Assetic_ID char(50), Shape_Length double, Shape_Area double, Asset_Subtype char(50), Asset_Type char(50)
    -> Reprojector_3
Reprojector_3
    DEST = EPSG:4326
    SOURCE = Read from feature
    RASTER_CELL_SIZE = Preserve Cells
    INTERPOLATION_TYPE_NAME = Nearest Neighbor
    STROKE_ARCS = Yes
    REPROJECTED -> GeometryExtractor_3
GeometryExtractor_3
    KIND_LONG = OGC Well Known Text
    ATTR = _geometry
    OGCVERSION = 1.1
    -> Boardwalk (writer CSV_1)
Boardwalk (writer CSV_1)
    attributes: Assetic_ID char(50), _geometry char(80)
Coaches_Box (reader GEODATABASE_MDB_1)
    attributes: geodb_oid integer, OBJECTID integer, PHOTO1 char(50), COMMENT char(50), SHAPE_X double, SHAPE_Y double, AST_NUM integer, NAME char(100), PG_MNTND integer, AMEND_DATE date, AMEND_BY char(20), AREA_ integer, VARIATION smallint, PATH char(200), SUB_TYPE char(15), STRUCT char(50), FUNCT char(50), COND_RATE char(50), C_STATUS char(50), TYPE char(50), COMP_TYPE char(50), Assetic_ID char(50), Asset_Subtype char(50), Asset_Type char(50)
    -> Reprojector_4
Reprojector_4
    DEST = EPSG:4326
    SOURCE = Read from feature
    RASTER_CELL_SIZE = Preserve Cells
    INTERPOLATION_TYPE_NAME = Nearest Neighbor
    STROKE_ARCS = Yes
    REPROJECTED -> GeometryExtractor_4
GeometryExtractor_4
    KIND_LONG = OGC Well Known Text
    ATTR = _geometry
    OGCVERSION = 1.1
    -> Coaches_Box (writer CSV_1)
Coaches_Box (writer CSV_1)
    attributes: Assetic_ID char(50), _geometry char(80)
Cricket_Pitch (reader GEODATABASE_MDB_1)
    attributes: geodb_oid integer, OBJECTID integer, AST_NUM integer, SURFACE char(50), SECONDARY_SURFACE char(50), PG_MNTND integer, LENGTH double, SEQUENCE smallint, AMEND_DATE date, AMEND_BY char(20), VARIATION smallint, COMMENTS char(200), PHOTO1 char(50), STRUCT char(50), FUNCT char(50), COND_RATE char(50), C_STATUS char(50), Asset_Subtype char(50), Assetic_ID char(50), Area_ double, Asset_Type char(50), Shape_Length double, Shape_Area double
    -> Reprojector_5
Reprojector_5
    DEST = EPSG:4326
    SOURCE = Read from feature
    RASTER_CELL_SIZE = Preserve Cells
    INTERPOLATION_TYPE_NAME = Nearest Neighbor
    STROKE_ARCS = Yes
    REPROJECTED -> GeometryExtractor_5
GeometryExtractor_5
    KIND_LONG = OGC Well Known Text
    ATTR = _geometry
    OGCVERSION = 1.1
    -> Cricket_Pitch (writer CSV_1)
Cricket_Pitch (writer CSV_1)
    attributes: Assetic_ID char(50), _geometry char(80)
DogOff_Leash (reader GEODATABASE_MDB_1)
    attributes: geodb_oid integer, OBJECTID integer, AST_NUM integer, TYPE char(50), SECONDARY_TYPE char(50), NAME char(100), PG_MNTND integer, AREA double, COMP_TYPE smallint, SEQUENCE smallint, AMEND_DATE date, AMEND_BY char(20), VARIATION smallint, COMMENTS char(200), PHOTO1 char(50), STRUCT char(50), FUNCT char(50), COND_RATE char(50), C_STATUS char(50), Area_ double, Shape_Length double, Shape_Area double, Asset_Type char(50), Assetic_ID char(50), Asset_Subtype char(50)
    -> Reprojector_6
Reprojector_6
    DEST = EPSG:4326
    SOURCE = Read from feature
    RASTER_CELL_SIZE = Preserve Cells
    INTERPOLATION_TYPE_NAME = Nearest Neighbor
    STROKE_ARCS = Yes
    REPROJECTED -> GeometryExtractor_6
GeometryExtractor_6
    KIND_LONG = OGC Well Known Text
    ATTR = _geometry
    OGCVERSION = 1.1
    -> DogOff_Leash (writer CSV_1)
DogOff_Leash (writer CSV_1)
    attributes: Assetic_ID char(50), _geometry char(80)
Drinking_Fountain (reader GEODATABASE_MDB_2)
    attributes: geodb_oid integer, OBJECTID integer, AST_NUM integer, TYPE char(50), PG_MNTND integer, COMP_TYPE smallint, SEQUENCE smallint, AMEND_DATE date, AMEND_BY char(20), VARIATION smallint, COMMENTS char(200), PHOTO1 char(50), STRUCT char(50), FUNCT char(50), COND_RATE char(50), C_STATUS char(50), In_ smallint, Asset_Subtype char(50), PATH char(250), Asset_Type char(50), Asset_ID char(255)
    -> Reprojector_7
Reprojector_7
    DEST = EPSG:4326
    SOURCE = Read from feature
    RASTER_CELL_SIZE = Preserve Cells
    INTERPOLATION_TYPE_NAME = Nearest Neighbor
    STROKE_ARCS = Yes
    REPROJECTED -> GeometryExtractor_7
GeometryExtractor_7
    KIND_LONG = OGC Well Known Text
    ATTR = _geometry
    OGCVERSION = 1.1
    -> Drinking_Fountain (writer CSV_1)
Drinking_Fountain (writer CSV_1)
    attributes: Asset_ID char(50), _geometry char(80)
Exercise_Fitness_Equipment (reader GEODATABASE_MDB_1)
    attributes: geodb_oid integer, OBJECTID_1 integer, Path char(119), Name char(28), Park char(100), Comments char(50), Assetic_ID char(50), PG_MNTND double, AST_NUM double, Asset_Subtype char(50), Asset_Type char(50)
    -> Reprojector_8
Reprojector_8
    DEST = EPSG:4326
    SOURCE = Read from feature
    RASTER_CELL_SIZE = Preserve Cells
    INTERPOLATION_TYPE_NAME = Nearest Neighbor
    STROKE_ARCS = Yes
    REPROJECTED -> GeometryExtractor_8
GeometryExtractor_8
    KIND_LONG = OGC Well Known Text
    ATTR = _geometry
    OGCVERSION = 1.1
    -> Exercise_Fitness_Equipment (writer CSV_1)
Exercise_Fitness_Equipment (writer CSV_1)
    attributes: Assetic_ID char(50), _geometry char(80)
Irrigated_Sites (reader GEODATABASE_MDB_1)
    attributes: geodb_oid integer, OBJECTID integer, SITE char(50), CLASSIFICATION char(50), OPERATIONAL char(4), Asset_Subclass char(50), Asset_Type char(50), Asset_Subtype char(50), AST_NUM double, Assetic_ID char(50), PG_MNTND integer
    -> Reprojector_12
Reprojector_12
    DEST = EPSG:4326
    SOURCE = Read from feature
    RASTER_CELL_SIZE = Preserve Cells
    INTERPOLATION_TYPE_NAME = Nearest Neighbor
    STROKE_ARCS = Yes
    REPROJECTED -> GeometryExtractor_12
GeometryExtractor_12
    KIND_LONG = OGC Well Known Text
    ATTR = _geometry
    OGCVERSION = 1.1
    -> Irrigated_Sites (writer CSV_1)
Irrigated_Sites (writer CSV_1)
    attributes: Assetic_ID char(50), _geometry char(80)
Irrigation_Controller (reader GEODATABASE_MDB_1)
    attributes: geodb_oid integer, OBJECTID integer, AST_NUM integer, PG_MNTND smallint, AMEND_DATE date, AMEND_BY char(50), SUB_TYPE char(25), Asset_Subt char(50), Controller smallint, Location char(254), Number_of integer, IRRinet__1 char(254), IRRinet__2 char(254), IRRinet__3 char(254), IRRinet__4 char(254), Power_Supp char(254), Modem_Type char(254), Cabinet char(254), Rain_Gauge char(254), Descriptio char(50), TYPE char(100), SECONDAR_1 char(100), NAME_2 char(100), SITE_1 char(100), HANDOV_DAT date, COMP_TYPE smallint, SUB char(50), PARCEL integer, Assetic_ID char(50), Asset_Type char(50),
      Asset_Subtype char(50), VARIATION smallint
    -> Reprojector_13
Reprojector_13
    DEST = EPSG:4326
    SOURCE = Read from feature
    RASTER_CELL_SIZE = Preserve Cells
    INTERPOLATION_TYPE_NAME = Nearest Neighbor
    STROKE_ARCS = Yes
    REPROJECTED -> GeometryExtractor_13
GeometryExtractor_13
    KIND_LONG = OGC Well Known Text
    ATTR = _geometry
    OGCVERSION = 1.1
    -> Irrigation_Controller (writer CSV_1)
Irrigation_Controller (writer CSV_1)
    attributes: Assetic_ID char(50), _geometry char(80)
IrrigationTank (reader GEODATABASE_MDB_1)
    attributes: geodb_oid integer, OBJECTID integer, AST_NUM integer, TYPE char(50), SECONDARY_TYPE char(50), PG_MNTND integer, COMP_TYPE smallint, SEQUENCE smallint, AMEND_DATE date, AMEND_BY char(3), FEATURE_TYPE char(25), VARIATION smallint, COMMENTS char(200), PHOTO1 char(50), STRUCT char(50), FUNCT char(50), COND_RATE char(50), C_STATUS char(50), Asset_Subtype char(50), Assetic_ID char(50), Asset_Type char(50)
    -> Reprojector_14
Reprojector_14
    DEST = EPSG:4326
    SOURCE = Read from feature
    RASTER_CELL_SIZE = Preserve Cells
    INTERPOLATION_TYPE_NAME = Nearest Neighbor
    STROKE_ARCS = Yes
    REPROJECTED -> GeometryExtractor_14
GeometryExtractor_14
    KIND_LONG = OGC Well Known Text
    ATTR = _geometry
    OGCVERSION = 1.1
    -> IrrigationTank (writer CSV_1)
IrrigationTank (writer CSV_1)
    attributes: Assetic_ID char(50), _geometry char(80)
Irrigration_pump (reader GEODATABASE_MDB_1)
    attributes: geodb_oid integer, OBJECTID integer, SITE_ASS_NUM integer, SITE char(50), PG_MNTND smallint, Asset_Subtype char(50), Brand_Model char(50), Assetic_ID char(50), Asset_Type char(50), VARIATION smallint
    -> Reprojector_15
Reprojector_15
    DEST = EPSG:4326
    SOURCE = Read from feature
    RASTER_CELL_SIZE = Preserve Cells
    INTERPOLATION_TYPE_NAME = Nearest Neighbor
    STROKE_ARCS = Yes
    REPROJECTED -> GeometryExtractor_15
GeometryExtractor_15
    KIND_LONG = OGC Well Known Text
    ATTR = _geometry
    OGCVERSION = 1.1
    -> Irrigration_pump (writer CSV_1)
Irrigration_pump (writer CSV_1)
    attributes: Assetic_ID char(50), _geometry char(80)
Parks_Light (reader GEODATABASE_MDB_1)
    attributes: geodb_oid integer, OBJECTID integer, AST_NUM integer, TYPE char(254), FEATURE_TY char(254), AUDIT_ID smallint, NAME char(254), COMMENTS char(254), PHOTO1 char(254), INSPECTOR char(254), POLE char(254), FIELD_TYPE char(254), PATH char(254), Assetic_ID char(50), Asset_Type char(50), Asset_Subtype char(50), PG_MNTND integer
    -> Reprojector_19
Reprojector_19
    DEST = EPSG:4326
    SOURCE = Read from feature
    RASTER_CELL_SIZE = Preserve Cells
    INTERPOLATION_TYPE_NAME = Nearest Neighbor
    STROKE_ARCS = Yes
    REPROJECTED -> GeometryExtractor_19
GeometryExtractor_19
    KIND_LONG = OGC Well Known Text
    ATTR = _geometry
    OGCVERSION = 1.1
    -> Parks_Light (writer CSV_1)
Parks_Light (writer CSV_1)
    attributes: Assetic_ID char(50), _geometry char(80)
PicnicTable (reader GEODATABASE_MDB_1)
    attributes: geodb_oid integer, OBJECTID integer, FID_Picnic integer, AST_NUM integer, TYPE char(50), PG_MNTND integer, COMP_TYPE smallint, SEQUENCE smallint, AMEND_DATE date, AMEND_BY char(20), VARIATION smallint, COMMENTS char(200), PHOTO1 char(50), STRUCT char(50), FUNCT char(50), COND_RATE char(50), C_STATUS char(50), Asset_Subtype char(50), PATH char(250), Assetic_ID char(50), Asset_Type char(50)
    -> Reprojector_22
Reprojector_22
    DEST = EPSG:4326
    SOURCE = Read from feature
    RASTER_CELL_SIZE = Preserve Cells
    INTERPOLATION_TYPE_NAME = Nearest Neighbor
    STROKE_ARCS = Yes
    REPROJECTED -> GeometryExtractor_22
GeometryExtractor_22
    KIND_LONG = OGC Well Known Text
    ATTR = _geometry
    OGCVERSION = 1.1
    -> PicnicTable (writer CSV_1)
PicnicTable (writer CSV_1)
    attributes: Assetic_ID char(50), _geometry char(80)
Playground (reader GEODATABASE_MDB_9)
    attributes: geodb_oid integer, OBJECTID integer, PLAYGROUND_ASS_NUM integer, SITE_ASS_NUM integer, TYPE char(50), SECONDARY_TYPE char(50), NAME char(100), RH_NUMBER char(16), PG_MNTND integer, AREA double, COMP_TYPE smallint, AMEND_DATE date, AMEND_BY char(20), FEATURE_TYPE char(50), Install_Date date, VARIATION smallint, COMMENTS char(200), PHOTO1 char(50), STRUCT char(50), FUNCT char(50), COND_RATE char(50), C_STATUS char(50), Path char(100), Assetic_ID char(50), Area_ double, Shape_Length double, Shape_Area double, Asset_Type char(50), Asset_Subtype char(50)
    -> Reprojector_24
Reprojector_24
    DEST = EPSG:4326
    SOURCE = Read from feature
    RASTER_CELL_SIZE = Preserve Cells
    INTERPOLATION_TYPE_NAME = Nearest Neighbor
    STROKE_ARCS = Yes
    REPROJECTED -> GeometryExtractor_24
GeometryExtractor_24
    KIND_LONG = OGC Well Known Text
    ATTR = _geometry
    OGCVERSION = 1.1
    -> Playground (writer CSV_1)
Playground (writer CSV_1)
    attributes: Assetic_ID char(50), _geometry char(80)
Seats (reader GEODATABASE_MDB_1)
    attributes: geodb_oid integer, OBJECTID integer, AST_NUM integer, TYPE char(50), PG_MNTND integer, SERIAL_NUM char(25), COMP_TYPE smallint, SEQUENCE smallint, AMEND_DATE date, AMEND_BY char(3), FEATURE_TYPE char(25), SUB_TYPE char(25), VARIATION smallint, COMMENTS char(200), PHOTO1 char(50), STRUCT char(50), FUNCT char(50), COND_RATE char(50), C_STATUS char(50), Asset_Subtype char(50), PATH char(250), Assetic_ID char(50), Asset_Type char(50)
    -> Reprojector_26
Reprojector_26
    DEST = EPSG:4326
    SOURCE = Read from feature
    RASTER_CELL_SIZE = Preserve Cells
    INTERPOLATION_TYPE_NAME = Nearest Neighbor
    STROKE_ARCS = Yes
    REPROJECTED -> GeometryExtractor_26
GeometryExtractor_26
    KIND_LONG = OGC Well Known Text
    ATTR = _geometry
    OGCVERSION = 1.1
    -> Seats (writer CSV_1)
Seats (writer CSV_1)
    attributes: Assetic_ID char(50), _geometry char(80)
Shelter (reader GEODATABASE_MDB_1)
    attributes: geodb_oid integer, OBJECTID integer, AST_NUM double, TYPE char(50), SECONDARY_ char(50), PG_MNTND double, COMP_TYPE double, SEQUENCE double, AMEND_DATE date, AMEND_BY char(20), VARIATION double, COMMENTS char(200), PHOTO1 char(50), STRUCT char(50), FUNCT char(50), COND_RATE char(50), C_STATUS char(50), SHAPE_LENG double, PATH char(200), Assetic_ID char(50), Shape_Length double, Shape_Area double, Asset_Type char(50), Asset_Subtype char(50)
    -> Reprojector_27
Reprojector_27
    DEST = EPSG:4326
    SOURCE = Read from feature
    RASTER_CELL_SIZE = Preserve Cells
    INTERPOLATION_TYPE_NAME = Nearest Neighbor
    STROKE_ARCS = Yes
    REPROJECTED -> GeometryExtractor_27
GeometryExtractor_27
    KIND_LONG = OGC Well Known Text
    ATTR = _geometry
    OGCVERSION = 1.1
    -> Shelter (writer CSV_1)
Shelter (writer CSV_1)
    attributes: Assetic_ID char(50), _geometry char(80)
Skate_BMX_Facility (reader GEODATABASE_MDB_1)
    attributes: geodb_oid integer, OBJECTID integer, AST_NUM integer, TYPE char(50), SECONDARY_ char(50), NAME char(100), AREA double, COMP_TYPE smallint, SEQUENCE smallint, AMEND_DATE date, AMEND_BY char(20), VARIATION smallint, COMMENTS char(200), PHOTO1 char(50), INSPECTOR char(20), INS_DATE date, STRUCT char(50), FUNCT char(50), COND_RATE char(50), C_STATUS char(50), PG_MNTND integer, Assetic_ID char(50), Area_ double, Shape_Length double, Shape_Area double, Asset_Subtype char(50), Asset_Type char(50)
    -> Reprojector_31
Reprojector_31
    DEST = EPSG:4326
    SOURCE = Read from feature
    RASTER_CELL_SIZE = Preserve Cells
    INTERPOLATION_TYPE_NAME = Nearest Neighbor
    STROKE_ARCS = Yes
    REPROJECTED -> GeometryExtractor_31
GeometryExtractor_31
    KIND_LONG = OGC Well Known Text
    ATTR = _geometry
    OGCVERSION = 1.1
    -> Skate_BMX_Facility (writer CSV_1)
Skate_BMX_Facility (writer CSV_1)
    attributes: Assetic_ID char(50), _geometry char(80)
Weather_Station (reader GEODATABASE_MDB_1)
    attributes: geodb_oid integer, OBJECTID_1 integer, AUDIT_ID double, NAME char(50), COMMENTS char(200), PHOTO1 char(50), INSPECTOR char(20), POLE char(50), FIELD_TYPE char(50), AXF_TIME_1 date, Path char(200), OBJECTID integer, AST_NUM integer, TYPE char(100), SECONDARY_TYPE char(100), NAME_1 char(100), SITE char(100), PG_MNTND integer, HANDOV_DAT date, COMP_TYPE smallint, AMEND_DATE date, AMEND_BY char(20), AREA_ integer, SUB char(50), STAGE smallint, PARCEL integer, VARIATION smallint, Maintain char(50), Asset_Subtype char(50), Assetic_ID char(50),
      Asset_Type char(50)
    -> Reprojector_42
Reprojector_42
    DEST = EPSG:4326
    SOURCE = Read from feature
    RASTER_CELL_SIZE = Preserve Cells
    INTERPOLATION_TYPE_NAME = Nearest Neighbor
    STROKE_ARCS = Yes
    REPROJECTED -> GeometryExtractor_42
GeometryExtractor_42
    KIND_LONG = OGC Well Known Text
    ATTR = _geometry
    OGCVERSION = 1.1
    -> Weather_Station (writer CSV_1)
Weather_Station (writer CSV_1)
    attributes: Assetic_ID char(50), _geometry char(80)
Windmill (reader GEODATABASE_MDB_1)
    attributes: geodb_oid integer, OBJECTID integer, AST_NUM integer, TYPE char(50), PG_MNTND integer, COMP_TYPE smallint, SEQUENCE smallint, AMEND_DATE date, AMEND_BY char(20), FEATURE_TYPE char(25), SUB_TYPE char(15), COMMENTS char(200), PHOTO1 char(50), STRUCT char(50), FUNCT char(50), COND_RATE char(50), C_STATUS char(50), VARIATION smallint, PHOTO char(250), Asset_Subtype char(50), Assetic_ID char(50), Asset_Type char(50)
    -> Reprojector_43
Reprojector_43
    DEST = EPSG:4326
    SOURCE = Read from feature
    RASTER_CELL_SIZE = Preserve Cells
    INTERPOLATION_TYPE_NAME = Nearest Neighbor
    STROKE_ARCS = Yes
    REPROJECTED -> GeometryExtractor_43
GeometryExtractor_43
    KIND_LONG = OGC Well Known Text
    ATTR = _geometry
    OGCVERSION = 1.1
    -> Windmill (writer CSV_1)
Windmill (writer CSV_1)
    attributes: Assetic_ID char(50), _geometry char(80)
Fence (reader GEODATABASE_MDB_3)
    attributes: geodb_oid integer, OBJECTID integer, AST_NUM integer, TYPE char(50), PG_MNTND integer, COMP_TYPE smallint, SEQUENCE smallint, AMEND_DATE date, AMEND_BY char(20), SUB_TYPE char(25), VARIATION smallint, COMMENTS char(200), PHOTO1 char(50), STRUCT char(50), FUNCT char(50), COND_RATE char(50), C_STATUS char(50), Length double, PATH char(250), Asset_Subtype char(50), Shape_Length double, Asset_Type char(50), Asset_ID char(255)
    -> Reprojector_9
Reprojector_9
    DEST = EPSG:4326
    SOURCE = Read from feature
    RASTER_CELL_SIZE = Preserve Cells
    INTERPOLATION_TYPE_NAME = Nearest Neighbor
    STROKE_ARCS = Yes
    REPROJECTED -> GeometryExtractor_9
GeometryExtractor_9
    KIND_LONG = OGC Well Known Text
    ATTR = _geometry
    OGCVERSION = 1.1
    -> Fence (writer CSV_1)
Fence (writer CSV_1)
    attributes: Asset_ID char(50), _geometry char(80)
GardenBed (reader GEODATABASE_MDB_4)
    attributes: geodb_oid integer, OBJECTID_1 integer, AST_NUM integer, TYPE char(50), SECONDARY_TYPE char(50), PG_MNTND integer, AREA double, COMP_TYPE smallint, SEQUENCE smallint, AMEND_DATE date, AMEND_BY char(20), VARIATION smallint, COMMENTS char(200), PHOTO1 char(50), STRUCT char(50), FUNCT char(50), COND_RATE char(50), C_STATUS char(50), Shape_Length double, Shape_Area double, Asset_Subtype char(50), Asset_Type char(50), SHAPE_1_Length double, SHAPE_1_Area double, Asset_ID char(255)
    -> Reprojector_10
Reprojector_10
    DEST = EPSG:4326
    SOURCE = Read from feature
    RASTER_CELL_SIZE = Preserve Cells
    INTERPOLATION_TYPE_NAME = Nearest Neighbor
    STROKE_ARCS = Yes
    REPROJECTED -> GeometryExtractor_10
GeometryExtractor_10
    KIND_LONG = OGC Well Known Text
    ATTR = _geometry
    OGCVERSION = 1.1
    -> GardenBed (writer CSV_1)
GardenBed (writer CSV_1)
    attributes: Asset_ID char(50), _geometry char(80)
Gate (reader GEODATABASE_MDB_5)
    attributes: geodb_oid integer, OBJECTID integer, AST_NUM integer, TYPE char(50), SECONDARY_TYPE char(50), PG_MNTND integer, LENGTH double, COMP_TYPE smallint, SEQUENCE smallint, AMEND_DATE date, AMEND_BY char(20), VARIATION smallint, COMMENTS char(200), PHOTO1 char(50), STRUCT char(50), FUNCT char(50), COND_RATE char(50), C_STATUS char(50), AssetSubClass char(250), PATH char(250), Asset_Subtype char(50), Shape_Length double, Asset_Type char(50), Asset_ID char(255)
    -> Reprojector_11
Reprojector_11
    DEST = EPSG:4326
    SOURCE = Read from feature
    RASTER_CELL_SIZE = Preserve Cells
    INTERPOLATION_TYPE_NAME = Nearest Neighbor
    STROKE_ARCS = Yes
    REPROJECTED -> GeometryExtractor_11
GeometryExtractor_11
    KIND_LONG = OGC Well Known Text
    ATTR = _geometry
    OGCVERSION = 1.1
    -> Gate (writer CSV_1)
Gate (writer CSV_1)
    attributes: Asset_ID char(50), _geometry char(80)
Memorial_Structure (reader GEODATABASE_MDB_6)
    attributes: geodb_oid integer, geodb_subtype_name char(254), OBJECTID integer, TYPE char(50), SECONDARY_TYPE char(50), PG_MNTND integer, COMP_TYPE smallint, SEQUENCE smallint, AMEND_DATE date, AMEND_BY char(20), VARIATION smallint, COMMENTS char(50), PHOTO1 char(50), STRUCT char(50), FUNCT char(50), COND_RATE char(50), C_STATUS char(50), AST_NUM integer, Photo_Link char(250), Asset_Subtype char(50), Asset_Type char(50), Asset_ID char(255)
    -> Reprojector_17
Reprojector_17
    DEST = EPSG:4326
    SOURCE = Read from feature
    RASTER_CELL_SIZE = Preserve Cells
    INTERPOLATION_TYPE_NAME = Nearest Neighbor
    STROKE_ARCS = Yes
    REPROJECTED -> GeometryExtractor_17
GeometryExtractor_17
    KIND_LONG = OGC Well Known Text
    ATTR = _geometry
    OGCVERSION = 1.1
    -> Irrigation_Controller00 (writer CSV_1)
Irrigation_Controller00 (writer CSV_1)
    attributes: Asset_ID char(50), _geometry char(80)
MowableArea (reader GEODATABASE_MDB_7)
    attributes: geodb_oid integer, OBJECTID integer, AREA double, AMEND_DATE date, AMEND_BY char(20), PG_MNTND integer, AST_NUM integer, COMP_TYPE smallint, SEQUENCE smallint, TYPE char(25), SUB_TYPE integer, VARIATION smallint, COMMENTS char(200), PHOTO1 char(50), STRUCT char(50), FUNCT char(50), COND_RATE char(50), C_STATUS char(50), Area_ double, Asset_Type char(50), Asset_Subtype char(50), Shape_Length double, Shape_Area double, Asset_ID char(255)
    -> Reprojector_18
Reprojector_18
    DEST = EPSG:4326
    SOURCE = Read from feature
    RASTER_CELL_SIZE = Preserve Cells
    INTERPOLATION_TYPE_NAME = Nearest Neighbor
    STROKE_ARCS = Yes
    REPROJECTED -> GeometryExtractor_18
GeometryExtractor_18
    KIND_LONG = OGC Well Known Text
    ATTR = _geometry
    OGCVERSION = 1.1
    -> Mowable_Area (writer CSV_1)
Mowable_Area (writer CSV_1)
    attributes: Asset_ID char(50), _geometry char(80)
Paths (reader GEODATABASE_MDB_8)
    attributes: geodb_oid integer, OBJECTID integer, AST_NUM integer, SURFACE char(50), SECONDARY_SURFACE char(50), PG_MNTND integer, COMP_TYPE smallint, SEQUENCE smallint, AMEND_DATE date, AMEND_BY char(20), VARIATION smallint, COMMENTS char(200), PHOTO1 char(50), STRUCT char(50), FUNCT char(50), COND_RATE char(50), C_STATUS char(50), Area_ double, Shape_Length double, Shape_Area double, Asset_Subtype char(50), Asset_Type char(50), Asset_ID char(255)
    -> Reprojector_21
Reprojector_21
    DEST = EPSG:4326
    SOURCE = Read from feature
    RASTER_CELL_SIZE = Preserve Cells
    INTERPOLATION_TYPE_NAME = Nearest Neighbor
    STROKE_ARCS = Yes
    REPROJECTED -> GeometryExtractor_21
GeometryExtractor_21
    KIND_LONG = OGC Well Known Text
    ATTR = _geometry
    OGCVERSION = 1.1
    -> Paths (writer CSV_1)
Paths (writer CSV_1)
    attributes: Asset_ID char(50), _geometry char(80)
Playground_Safety_Surfacing (reader GEODATABASE_MDB_10)
    attributes: geodb_oid integer, OBJECTID integer, AREA double, COMMENTS char(200), PHOTO1 char(50), Path char(100), Shape_Leng double, RH_NUMBER_ char(16), Type char(50), Install_Da date, Assetic_ID char(50), FUNCT char(50), STRUCT char(50), NAME char(100), SECONDARY_ char(50), FEATURE_TY char(50), VARIATION smallint, COND_RATE char(50), C_STATUS char(50), AMEND_BY char(50), AMEND_DATE date, PLAYGROUND integer, COMP_TYPE smallint, Shape_Length double, Shape_Area double, Asset_Subtype char(50), Asset_Type char(50), AST_NUM double, PG_MNTND integer
    -> Reprojector_16
Reprojector_16
    DEST = EPSG:4326
    SOURCE = Read from feature
    RASTER_CELL_SIZE = Preserve Cells
    INTERPOLATION_TYPE_NAME = Nearest Neighbor
    STROKE_ARCS = Yes
    REPROJECTED -> GeometryExtractor_16
GeometryExtractor_16
    KIND_LONG = OGC Well Known Text
    ATTR = _geometry
    OGCVERSION = 1.1
    -> Playground_Safety_Surfacing (writer CSV_1)
Playground_Safety_Surfacing (writer CSV_1)
    attributes: Assetic_ID char(50), _geometry char(80)
Public_Art (reader GEODATABASE_MDB_11)
    attributes: geodb_oid integer, OBJECTID integer, TYPE char(50), SECONDARY_TYPE char(50), COMP_TYPE smallint, SEQUENCE smallint, AMEND_DATE date, AMEND_BY char(20), VARIATION smallint, COMMENTS char(50), PHOTO1 char(50), STRUCT char(50), FUNCT char(50), COND_RATE char(50), C_STATUS char(50), AST_NUM integer, Photo_Link char(250), Asset_Subtype char(50), Asset_Type char(50), PG_MNTND integer, Asset_ID char(255)
    -> Reprojector_25
Reprojector_25
    DEST = EPSG:4326
    SOURCE = Read from feature
    RASTER_CELL_SIZE = Preserve Cells
    INTERPOLATION_TYPE_NAME = Nearest Neighbor
    STROKE_ARCS = Yes
    REPROJECTED -> GeometryExtractor_25
GeometryExtractor_25
    KIND_LONG = OGC Well Known Text
    ATTR = _geometry
    OGCVERSION = 1.1
    -> Public_Art (writer CSV_1)
Public_Art (writer CSV_1)
    attributes: Asset_ID char(50), _geometry char(80)
Sign (reader GEODATABASE_MDB_12)
    attributes: geodb_oid integer, OBJECTID integer, AST_NUM integer, TYPE char(50), PG_MNTND integer, AUDIT_ID char(6), SEQUENCE smallint, COMP_TYPE smallint, AMEND_DATE date, AMEND_BY char(20), CATEGORY char(100), SUBURB char(50), PHOTO char(50), COMMENTS char(200), VARIATION smallint, STRUCT char(50), FUNCT char(50), COND_RATE char(50), C_STATUS char(50), Asset_Type char(50), Asset_Subtype char(50), Asset_ID char(255)
    -> Reprojector_28
Reprojector_28
    DEST = EPSG:4326
    SOURCE = Read from feature
    RASTER_CELL_SIZE = Preserve Cells
    INTERPOLATION_TYPE_NAME = Nearest Neighbor
    STROKE_ARCS = Yes
    REPROJECTED -> GeometryExtractor_28
GeometryExtractor_28
    KIND_LONG = OGC Well Known Text
    ATTR = _geometry
    OGCVERSION = 1.1
    -> Sign (writer CSV_1)
Sign (writer CSV_1)
    attributes: Asset_ID char(50), _geometry char(80)
Site (reader GEODATABASE_MDB_13)
    attributes: geodb_oid integer, OBJECTID integer, NAME char(100), Asset_Subtype char(50), AST_NUM integer, TYPE char(100), SECONDARY_TYPE char(100), SITE char(100), PG_MNTND integer, HANDOV_DAT date, COMP_TYPE smallint, AMEND_DATE date, AMEND_BY char(20), SUB char(50), STAGE smallint, PARCEL integer, VARIATION smallint, Maintain char(50), ID2 char(50), comments char(50), Shape_Length_1 double, Shape_Area_1 double, Asset_Type char(50), Shape_Length double, Shape_Area double, Estate_Name_and_Stage char(200), doc_num integer, Certified date, Asset_ID char(255)
    -> Reprojector_30
Reprojector_30
    DEST = EPSG:4326
    SOURCE = Read from feature
    RASTER_CELL_SIZE = Preserve Cells
    INTERPOLATION_TYPE_NAME = Nearest Neighbor
    STROKE_ARCS = Yes
    REPROJECTED -> GeometryExtractor_30
GeometryExtractor_30
    KIND_LONG = OGC Well Known Text
    ATTR = _geometry
    OGCVERSION = 1.1
    -> Site (writer CSV_1)
Site (writer CSV_1)
    attributes: Asset_ID char(50), _geometry char(80)
SportingGoal (reader GEODATABASE_MDB_14)
    attributes: geodb_oid integer, OBJECTID integer, MATERIAL char(120), COMMENTS char(250), PHOTO1 char(25), PHOTO1PATH char(250), SITE_NAME char(120), SITE_ID char(20), PARCEL_NUM char(15), INSPECTOR char(20), INS_DATE date, STRUCT char(20), FUNCT char(20), COND_RATE char(20), GEODB_TYPE char(50), C_STATUS char(15), AST_NUM integer, TYPE char(50), SECONDARY_ char(50), PG_MNTND integer, COMP_TYPE integer, SEQUENCE integer, AMEND_DATE date, SUB_TYPE char(20), BIN_ID integer, BIN_TYPE char(3), MANUFACTUR char(50), LIGHT_LOCA char(50), AUDIT_REFE char(50), INSTALLED smallint,
      NAME char(50), LIGHTING_S char(15), FINALISED char(10), CATEGORY char(100), SIZE_ double, FEATURE char(24), STATUS char(80), PLACE_NAME char(100), AMEND_BY char(20), FEATURE_TYPE char(25), Variation smallint, Asset_Subtype char(50), Asset_Type char(50), Asset_ID char(255)
    -> Reprojector_32
Reprojector_32
    DEST = EPSG:4326
    SOURCE = Read from feature
    RASTER_CELL_SIZE = Preserve Cells
    INTERPOLATION_TYPE_NAME = Nearest Neighbor
    STROKE_ARCS = Yes
    REPROJECTED -> GeometryExtractor_32
GeometryExtractor_32
    KIND_LONG = OGC Well Known Text
    ATTR = _geometry
    OGCVERSION = 1.1
    -> Skate_BMX_Facility00 (writer CSV_1)
Skate_BMX_Facility00 (writer CSV_1)
    attributes: Asset_ID char(50), _geometry char(80)
SportsArea (reader GEODATABASE_MDB_15)
    attributes: geodb_oid integer, OBJECTID integer, AST_NUM integer, TYPE char(50), SECONDARY_TYPE char(50), NAME char(100), PG_MNTND integer, AREA double, COMP_TYPE smallint, SEQUENCE smallint, AMEND_DATE date, AMEND_BY char(20), VARIATION smallint, COMMENTS char(200), PHOTO1 char(50), STRUCT char(50), FUNCT char(50), COND_RATE char(50), C_STATUS char(50), Area_ double, Shape_Length double, Shape_Area double, Asset_Type char(50), Photo_Link char(250), Asset_Subtype char(50), Asset_ID char(255)
    -> Reprojector_33
Reprojector_33
    DEST = EPSG:4326
    SOURCE = Read from feature
    RASTER_CELL_SIZE = Preserve Cells
    INTERPOLATION_TYPE_NAME = Nearest Neighbor
    STROKE_ARCS = Yes
    REPROJECTED -> GeometryExtractor_33
GeometryExtractor_33
    KIND_LONG = OGC Well Known Text
    ATTR = _geometry
    OGCVERSION = 1.1
    -> SportsArea (writer CSV_1)
SportsArea (writer CSV_1)
    attributes: Asset_ID char(50), _geometry char(80)
Sportsfield (reader GEODATABASE_MDB_16)
    attributes: geodb_oid integer, OBJECTID integer, AST_NUM integer, TYPE char(50), SECONDARY_TYPE char(50), NAME char(50), PG_MNTND integer, AREA double, COMP_TYPE smallint, SEQUENCE smallint, AMEND_DATE date, AMEND_BY char(20), BOUNDARY_LENGTH smallint, VARIATION smallint, COMMENTS char(200), PHOTO1 char(50), STRUCT char(50), FUNCT char(50), COND_RATE char(50), C_STATUS char(50), Area_ double, Shape_Length double, Shape_Area double, Asset_Type char(50), Asset_Subtype char(50), Photo_Link char(250), Asset_ID char(255)
    -> Reprojector_34
Reprojector_34
    DEST = EPSG:4326
    SOURCE = Read from feature
    RASTER_CELL_SIZE = Preserve Cells
    INTERPOLATION_TYPE_NAME = Nearest Neighbor
    STROKE_ARCS = Yes
    REPROJECTED -> GeometryExtractor_34
GeometryExtractor_34
    KIND_LONG = OGC Well Known Text
    ATTR = _geometry
    OGCVERSION = 1.1
    -> SportsField (writer CSV_1)
SportsField (writer CSV_1)
    attributes: Asset_ID char(50), _geometry char(80)
TennisCourt (reader GEODATABASE_MDB_17)
    attributes: geodb_oid integer, OBJECTID integer, AST_NUM integer, SURFACE char(50), SECONDARY_SURFACE char(50), NAME char(100), SITE char(100), PG_MNTND integer, AREA double, TENANT char(50), CONSTRUCTED smallint, RENOVATED smallint, COMP_TYPE smallint, SEQUENCE smallint, AMEND_DATE date, AMEND_BY char(20), FEATURE_TYPE char(50), VARIATION smallint, COMMENTS char(200), PHOTO1 char(50), STRUCT char(50), FUNCT char(50), COND_RATE char(50), C_STATUS char(50), Area_ double, Shape_Length double, Shape_Area double, Asset_Type char(50), Asset_Subtype char(50), Photo_Link char(250),
      Asset_ID char(255)
    -> Reprojector_36
Reprojector_36
    DEST = EPSG:4326
    SOURCE = Read from feature
    RASTER_CELL_SIZE = Preserve Cells
    INTERPOLATION_TYPE_NAME = Nearest Neighbor
    STROKE_ARCS = Yes
    REPROJECTED -> GeometryExtractor_36
GeometryExtractor_36
    KIND_LONG = OGC Well Known Text
    ATTR = _geometry
    OGCVERSION = 1.1
    -> TennisCourt (writer CSV_1)
TennisCourt (writer CSV_1)
    attributes: Asset_ID char(50), _geometry char(80)
Turf_Active (reader GEODATABASE_MDB_17)
    attributes: geodb_oid integer, OBJECTID integer, AST_NUM integer, TYPE char(50), SECONDARY_TYPE char(50), NAME char(50), PG_MNTND integer, AREA double, COMP_TYPE smallint, SEQUENCE smallint, AMEND_DATE date, AMEND_BY char(20), VARIATION smallint, COMMENTS char(200), PHOTO1 char(50), INSPECTOR char(20), INS_DATE date, EASTING double, NORTHING double, LATITUDE double, LONGITUDE double, UTC_TIME char(50), STRUCT char(50), FUNCT char(50), COND_RATE char(50), C_STATUS char(50), Asset_Type char(50), Asset_Subtype char(50), HANDOV_DAT date, Assetic_ID char(50),
      Shape_Length double, Shape_Area double
    -> Reprojector_38
Reprojector_38
    DEST = EPSG:4326
    SOURCE = Read from feature
    RASTER_CELL_SIZE = Preserve Cells
    INTERPOLATION_TYPE_NAME = Nearest Neighbor
    STROKE_ARCS = Yes
    REPROJECTED -> GeometryExtractor_38
GeometryExtractor_38
    KIND_LONG = OGC Well Known Text
    ATTR = _geometry
    OGCVERSION = 1.1
    -> Turf_Active (writer CSV_1)
Turf_Active (writer CSV_1)
    attributes: _geometry char(80), Assetic_ID char(80)
Water_Meter (reader GEODATABASE_MDB_17)
    attributes: geodb_oid integer, OBJECTID_1 integer, OBJECTID integer, METER_NUMB char(50), SITE_NAME char(50), TYPE char(50), CAPACITY char(50), IRRINET_ID char(15), FEATURE_TY char(25), SUB_TYPE char(50), Comments char(50), Asset_Type char(50), PG_MNTND double, AST_NUM integer, Asset_Subtype char(50), VARIATION smallint, Asset_ID char(255)
    -> Reprojector_40
Reprojector_40
    DEST = EPSG:4326
    SOURCE = Read from feature
    RASTER_CELL_SIZE = Preserve Cells
    INTERPOLATION_TYPE_NAME = Nearest Neighbor
    STROKE_ARCS = Yes
    REPROJECTED -> GeometryExtractor_40
GeometryExtractor_40
    KIND_LONG = OGC Well Known Text
    ATTR = _geometry
    OGCVERSION = 1.1
    -> Water_Meter (writer CSV_1)
Water_Meter (writer CSV_1)
    attributes: Asset_ID char(80), _geometry char(80)
WaterBody (reader GEODATABASE_MDB_17)
    attributes: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
TopiaryTree (reader GEODATABASE_MDB_17)
    attributes: geodb_oid integer, OBJECTID integer, AST_NUM integer, TYPE char(50), SECONDARY_TYPE char(50), PG_MNTND integer, AREA double, COMP_TYPE smallint, SEQUENCE smallint, AMEND_DATE date, AMEND_BY char(20), VARIATION smallint, COMMENTS char(200), PHOTO1 char(50), STRUCT char(50), FUNCT char(50), COND_RATE char(50), C_STATUS char(50), Area_ double, Asset_Subtype char(50), Asset_Type char(50), Asset_ID char(255)
    -> Reprojector_37
Reprojector_37
    DEST = EPSG:4326
    SOURCE = Read from feature
    RASTER_CELL_SIZE = Preserve Cells
    INTERPOLATION_TYPE_NAME = Nearest Neighbor
    STROKE_ARCS = Yes
    REPROJECTED -> GeometryExtractor_37
GeometryExtractor_37
    KIND_LONG = OGC Well Known Text
    ATTR = _geometry
    OGCVERSION = 1.1
    -> TopiaryTree (writer CSV_1)
TopiaryTree (writer CSV_1)
    attributes: Asset_ID char(80), _geometry char(80)
Wall (reader GEODATABASE_MDB_18)
    attributes: geodb_oid integer, OBJECTID_1 integer, AST_NUM integer, TYPE char(50), PG_MNTND integer, LENGTH double, COMP_TYPE smallint, SEQUENCE smallint, AMEND_DATE date, AMEND_BY char(20), SUB_TYPE char(25), VARIATION smallint, COMMENTS char(200), PHOTO1 char(50), INSPECTOR char(20), INS_DATE date, EASTING double, NORTHING double, STRUCT char(50), FUNCT char(50), COND_RATE char(50), C_STATUS char(50), HWOOD_ID double, Shape_Leng double, Asset_Subtype char(50), PATH char(250), Shape_Length double, Asset_Type char(50), Asset_ID char(255)
    -> Reprojector_39
Reprojector_39
    DEST = EPSG:4326
    SOURCE = Read from feature
    RASTER_CELL_SIZE = Preserve Cells
    INTERPOLATION_TYPE_NAME = Nearest Neighbor
    STROKE_ARCS = Yes
    REPROJECTED -> GeometryExtractor_39
GeometryExtractor_39
    KIND_LONG = OGC Well Known Text
    ATTR = _geometry
    OGCVERSION = 1.1
    -> Wall (writer CSV_1)
Wall (writer CSV_1)
    attributes: _geometry char(80), Asset_ID char(80)
Reprojector_41
    DEST = EPSG:4326
    SOURCE = Read from feature
    RASTER_CELL_SIZE = Preserve Cells
    INTERPOLATION_TYPE_NAME = Nearest Neighbor
    STROKE_ARCS = Yes
    REPROJECTED -> GeometryExtractor_41
GeometryExtractor_41
    KIND_LONG = OGC Well Known Text
    ATTR = _geometry
    OGCVERSION = 1.1
    -> WaterBody (writer CSV_1)
WaterBody (writer CSV_1)
    attributes: Asset_ID char(80), _geometry char(80)
